(defun c:gele()
   (setq taskas1 (getpoint "\n Iveskite kampinio kairiojo tasko koordinates (x,y):"))
   (setq taskas2 (list (-(car taskas1) 20)(+(cadr taskas1) 60)))
   (setq taskas3 (list (+(car taskas2) 40)(cadr taskas2)))
   (setq taskas4 (list (+(car taskas3) 40)(cadr taskas3)))
   (setq taskas5 (list (-(car taskas4) 20)(-(cadr taskas4) 60)))
  (command "LINE" taskas1 taskas2 taskas3 taskas4 taskas5 "C")
  (setq lapas1 (list (+(car taskas3) 50)(+(cadr taskas3) 40)))
(setq lapas2 (list (+(car lapas1) 20)(-(cadr lapas1) 25)))
(command "LINE" taskas3 lapas1 lapas2 "C")
   (setq taskas6 (list (car taskas3)(+(cadr taskas3) 80)))
  (command "LINE" taskas3 taskas6 "")
  (setq spindulys 30)
  (setq centras (list (car taskas6)(+(cadr taskas6) 30 )))
    (command "CIRCLE"  centras spindulys )
;braizome ziedlapius
  (setq centras1 (list (+(car centras) 30)(cadr centras)))
  (setq centras2 (list (car centras)(-(cadr centras) 30)))
  (setq centras3 (list (-(car centras) 30)(cadr centras)))
  (setq centras4 (list (car centras)(+(cadr centras) 30)))
  (command "COLOR" "red")
  (command "CIRCLE" centras1 30)
  	(command "COLOR" "green")   
  (command "CIRCLE" centras2 30)
  (command "COLOR" "white")
(command "CIRCLE" centras3 30)
  (command "COLOR" "green")
(command "CIRCLE" centras4 30))
