(defun C:laivas()
  (setq t1 (getpoint "\n Iveskite pradzios koordinates:"))
  (setq t2 (list (+(car t1) 45)(-(cadr t1) 3)))
  (setq t3 (list (+(car t1) 130)(cadr t1)))
  (setq b1 (list (-(car t1) 23)(-(cadr t1) 25)))
  (setq b2 (list (+(car b1) 35)(+(cadr b1) 8)))
  (setq b3 (list (+(car b1) 62)(-(cadr b1) 5)))
  (setq b4 (list (+(car b3) 34)(+(cadr b3) 14)))
  (setq b5 (list (+(car b4) 35)(-(cadr b4) 11)))
  (setq b6 (list (+(car b5) 33)(+(cadr b5) 10)))
  (setq t4 (list (+(car t1) 18)(-(cadr t1) 19.5)))
  (setq t5 (list (-(car t3) 22)(-(cadr t3) 27)))
  (setq v1 (list (+(car t1) 63.5)(-(cadr t1) 2.8)))
  (setq v2 (list (+(car t1) 66.5)(-(cadr t1) 2.8)))
  (setq v3 (list (car v1)(+(cadr v1) 60)))
  (setq v4 (list (car v2)(+(cadr v2) 60)))
  (setq f1 (list (car v2)(+(cadr v2) 16)))
  (setq f2 (list (+(car f1) 12)(+(cadr f1) 20)))
  (setq f3 (list (+(car f1) 40)(cadr f1)))
  (setq f4 (list (+(car f1) 20)(+(cadr f1) 5)))
  (setq f5 (list (+(car f1) 37)(+(cadr f1) 20)))
  (setq f6 (list (+(car f1) 20)(+(cadr f1) 3)))
  (command "ARC" t1 t2 t3 "")
  (command "SPLINE" b1 b2 b3 b4 b5 b6 "" "" "")
  (command "OSNAP" "OFF")
  (command "LINE" t1 t4 "")
  (command "LINE" t3 t5 "")
  (command "LINE" v1 v3 "")
  (command "LINE" v2 v4 "")
  (command "LINE" v3 v4 "")
  (command "ARC" f1 f2 v4 "")
  (command "ARC" v4 f5 f3 "")
  (command "ARC" f3 f4 f1 "")
  (command "hatch" "solid" f1 f2 v4 f5 f3 f4 ""))
