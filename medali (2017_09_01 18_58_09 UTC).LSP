(defun C:medalis()
  (SETQ Taskas1 (getpoint "\n Iveskite tasko Taskas1 koordinates:"))
  (SETQ Taskas2 (getpoint "\n Iveskite tasko Taskas2 koordinates:"))
  (SETQ Taskas3 (getpoint "\n Iveskite tasko Taskas3 koordinates:"))
  (SETQ Taskas4 (getpoint "\n Iveskite tasko Taskas4 koordinates:"))
  (command "LINE" Taskas1 Taskas2 Taskas3 taskas4 "C")
  (SETQ spindulys (getreal "\n Iveskite spinduli:"))
  (setq centras (getpoint "\n Iveskite pradzios koordinates:"))
  (command "CIRCLE" centras spindulys))
